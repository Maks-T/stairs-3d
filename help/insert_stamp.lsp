(vl-load-com)

(defun c:GOST_STAMP ( / *error* doc pt0 sc draw-line draw-text y)
  (setq doc (vla-get-ActiveDocument (vlax-get-acad-object)))
  (vla-StartUndoMark doc)

  ;; Обработчик ошибок для корректного завершения отмены
  (defun *error* (msg)
    (vla-EndUndoMark doc)
    (if (and msg (not (wcmatch (strcase msg t) "*cancel*,*exit*")))
      (princ (strcat "\nОшибка: " msg))
    )
    (princ)
  )

  ;; Запрос точки у пользователя
  (setq pt0 (getpoint "\nУкажите правый нижний угол рамки: "))

  (if pt0
    (progn
      ;; Запрос масштаба (по умолчанию 16, т.к. ваша рамка увеличена в 16 раз)
      (setq sc (getreal "\nВведите масштаб штампа <16.0>: "))
      (if (null sc) (setq sc 16.0))

      ;; Вспомогательная функция рисования линии с весом (DXF 370: 50 = 0.5 мм, 25 = 0.25 мм)
      (defun draw-line (p1 p2 lw / )
        (entmake (list
          '(0 . "LINE")
          (cons 10 (list (+ (car pt0) (* (car p1) sc)) (+ (cadr pt0) (* (cadr p1) sc)) 0.0))
          (cons 11 (list (+ (car pt0) (* (car p2) sc)) (+ (cadr pt0) (* (cadr p2) sc)) 0.0))
          (cons 370 lw)
        ))
      )

      ;; Вспомогательная функция добавления текста
      (defun draw-text (txt pt h align / p)
        (setq p (list (+ (car pt0) (* (car pt) sc)) (+ (cadr pt0) (* (cadr pt) sc)) 0.0))
        (if (= align "C")
          (entmake (list
            '(0 . "TEXT")
            (cons 1 txt)
            (cons 10 p)
            (cons 11 p)
            (cons 40 (* h sc))
            '(72 . 1) ; Выравнивание по центру
            '(73 . 2) ; Выравнивание по середине
          ))
          (entmake (list
            '(0 . "TEXT")
            (cons 1 txt)
            (cons 10 p)
            (cons 40 (* h sc))
            '(72 . 0) ; По левому краю
            '(73 . 0)
          ))
        )
      )

      ;; ================= ОСНОВНЫЕ ТОЛСТЫЕ ЛИНИИ (0.50 мм) =================
      ;; Внешний контур 185х55
      (draw-line '(-185.0 0.0) '(0.0 0.0) 50)
      (draw-line '(-185.0 55.0) '(0.0 55.0) 50)
      (draw-line '(-185.0 0.0) '(-185.0 55.0) 50)
      (draw-line '(0.0 0.0) '(0.0 55.0) 50)

      ;; Границы крупных блоков
      (draw-line '(-120.0 0.0) '(-120.0 55.0) 50)   ; Разделитель левой колонки (65 мм от края)
      (draw-line '(-120.0 40.0) '(0.0 40.0) 50)     ; Линия под обозначением документа
      (draw-line '(-50.0 0.0) '(-50.0 40.0) 50)     ; Разделитель блока наименования и правого блока
      (draw-line '(-120.0 15.0) '(0.0 15.0) 50)     ; Линия под материалом и над предприятием

      ;; ================= ТОНКИЕ ЛИНИИ (0.25 мм) =================
      ;; Левый блок (строки фамилий и изменений с шагом 5 мм)
      (setq y 5.0)
      (while (<= y 50.0)
        (if (not (= y 15.0)) ; 15 мм уже нарисована толстой
          (draw-line (list -185.0 y) (list -120.0 y) 25)
        )
        (setq y (+ y 5.0))
      )

      ;; Вертикальные линии левого блока
      (draw-line '(-178.0 35.0) '(-178.0 55.0) 25)  ; Колонка «Изм.» (7 мм)
      (draw-line '(-168.0 0.0) '(-168.0 55.0) 25)   ; Колонка «Лист / Должности» (10 мм)
      (draw-line '(-145.0 0.0) '(-145.0 55.0) 25)   ; Колонка «№ докум. / Фамилии» (23 мм)
      (draw-line '(-130.0 0.0) '(-130.0 55.0) 25)   ; Колонка «Подпись» (15 мм)

      ;; Линии правого верхнего блока (Литера, Масса, Масштаб)
      (draw-line '(-50.0 35.0) '(0.0 35.0) 25)
      (draw-line '(-50.0 20.0) '(0.0 20.0) 25)
      (draw-line '(-35.0 20.0) '(-35.0 40.0) 25)   ; Литера (15 мм)
      (draw-line '(-18.0 20.0) '(-18.0 40.0) 25)   ; Масса (17 мм)

      ;; Разделитель колонок «Лист» и «Листов»
      (draw-line '(-30.0 15.0) '(-30.0 20.0) 25)

      ;; ================= НАДПИСИ (ГОСТ) =================
      ;; Должности слева
      (draw-text "Разраб."   '(-183.0 26.0) 2.3 "L")
      (draw-text "Пров."     '(-183.0 21.0) 2.3 "L")
      (draw-text "Т. контр." '(-183.0 16.0) 2.3 "L")
      (draw-text "Н. контр." '(-183.0 6.0)  2.3 "L")
      (draw-text "Утв."      '(-183.0 1.0)  2.3 "L")

      ;; Шапка таблицы изменений
      (draw-text "Изм."      '(-181.5 52.5) 2.0 "C")
      (draw-text "Лист"      '(-173.0 52.5) 2.0 "C")
      (draw-text "№ докум."  '(-156.5 52.5) 2.0 "C")
      (draw-text "Подп."     '(-137.5 52.5) 2.0 "C")
      (draw-text "Дата"      '(-125.0 52.5) 2.0 "C")

      ;; Шапка блока справа
      (draw-text "Лит."      '(-42.5 37.5) 2.3 "C")
      (draw-text "Масса"     '(-26.5 37.5) 2.3 "C")
      (draw-text "Масштаб"   '(-9.0 37.5)  2.3 "C")
      (draw-text "Лист"      '(-40.0 17.5) 2.3 "C")
      (draw-text "Листов"    '(-15.0 17.5) 2.3 "C")

      ;; Включение отображения весов линий
      (setvar "LWDISPLAY" 1)

      (princ "\nШтамп успешно построен!")
    )
  )

  (vla-EndUndoMark doc)
  (princ)
)
